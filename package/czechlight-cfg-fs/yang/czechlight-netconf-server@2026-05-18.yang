module czechlight-netconf-server {
  yang-version 1.1;
  namespace "http://czechlight.cesnet.cz/yang/czechlight-netconf-server";
  prefix "czechlight-netconf-server";

  import ietf-netconf-server {
    prefix ncs;
  }

  import libnetconf2-netconf-server {
    prefix np2;
  }

  organization "CESNET";
  contact "photonics@cesnet.cz";
  description "Failsafes for NETCONF server configuration";

  revision 2026-05-18 {
    description "YANG updates";
  }

  revision 2025-12-01 {
    description "YANG updates";
  }

  revision 2025-11-05 {
    description "UNIX socket";
  }

  revision 2024-09-04 {
    description "Initial release";
  }

  deviation /ncs:netconf-server {
    deviate add {
      must "count(listen) = 1" {
        error-message "The NETCONF server must be activated for listening at some endpoint";
      }
    }
  }

  deviation /ncs:netconf-server/ncs:listen/ncs:endpoints {
    deviate add {
      must "count(endpoint/ssh) >= 1" {
        error-message "The NETCONF server must enable at least one SSH endpoint";
      }
    }

    deviate add {
      must "count(endpoint/np2:unix) >= 1" {
        error-message "The UNIX socket path of the NETCONF server must be present";
      }
    }
  }

  deviation /ncs:netconf-server/ncs:listen/ncs:endpoints/ncs:endpoint/ncs:transport/np2:unix/np2:unix {
    deviate add {
      must "count(hidden-path) = 1" {
        error-message "The UNIX socket path cannot be changed";
      }
    }

    deviate add {
      must "socket-permissions/mode = '0666' and count(socket-permissions/owner) = 0 and count(socket-permissions/group) = 0" {
        error-message "The UNIX socket permissions and ownership cannot be changed";
      }
    }

    deviate add {
      must "count(client-authentication/user-mapping) = 0" {
        error-message "User mapping at UNIX socket is not allowed";
      }
    }
  }
}
