module czechlight-netconf-server {
  yang-version 1.1;
  namespace "http://czechlight.cesnet.cz/yang/czechlight-netconf-server";
  prefix "czechlight-netconf-server";

  import ietf-netconf-server {
    prefix ncs;
    revision-date '2023-12-28';
  }

  organization "CESNET";
  contact "photonics@cesnet.cz";
  description "Failsafes for NETCONF server configuration";

  revision 2024-09-04 {
    description "Initial release";
  }

  deviation /ncs:netconf-server {
    deviate add {
      must "count(listen) = 1" {
        error-message "The NETCONF server must be activated for listening at some endpoint";
      }
    }
  }

  deviation /ncs:netconf-server/ncs:listen/ncs:endpoints {
    deviate add {
      must "count(endpoint/ssh) >= 1" {
        error-message "The NETCONF server must enable at least one SSH endpoint";
      }
    }
  }
}
